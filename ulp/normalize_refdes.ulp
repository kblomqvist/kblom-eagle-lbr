#usage "<b>Normalize ref-des' font, size and ratio.</b>"
       "<p>Usage: CHANGE grid to mils and run normalize_refdes.ulp"
       "<p>Author: Kim Blomqvist"
       "<p><i>License: Attribution 3.0 Unported (CC BY 3.0)</i>"

string refdes_font = "VECTOR";  // VECTOR | PROPORTIONAL | FIXED
int refdes_size = 30;           // mils
int refdes_ratio = 16;          // percents

string nrefdes_cmd;
string nrefdes_c;

if (board) {
    board(B) {
        B.elements(E) {
            E.texts(T) {
                sprintf(nrefdes_c, "CHANGE FONT %s (%.2f %.2f);\n", refdes_font, u2mil(T.x), u2mil(T.y));
                nrefdes_cmd += nrefdes_c;

                sprintf(nrefdes_c, "CHANGE SIZE %d (%.2f %.2f);\n", refdes_size, u2mil(T.x), u2mil(T.y));
                nrefdes_cmd += nrefdes_c;

                sprintf(nrefdes_c, "CHANGE RATIO %d (%.2f %.2f);\n", refdes_ratio, u2mil(T.x), u2mil(T.y));
                nrefdes_cmd += nrefdes_c;
            }
        }
        B.texts(T) {
                sprintf(nrefdes_c, "CHANGE FONT %s (%.2f %.2f);\n", refdes_font, u2mil(T.x), u2mil(T.y));
                nrefdes_cmd += nrefdes_c;

                sprintf(nrefdes_c, "CHANGE SIZE %d (%.2f %.2f);\n", refdes_size, u2mil(T.x), u2mil(T.y));
                nrefdes_cmd += nrefdes_c;

                sprintf(nrefdes_c, "CHANGE RATIO %d (%.2f %.2f);\n", refdes_ratio, u2mil(T.x), u2mil(T.y));
                nrefdes_cmd += nrefdes_c;
        }
    }
}

exit(nrefdes_cmd); // puke up
